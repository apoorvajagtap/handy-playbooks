module Cisco-IOS-XR-plat-chas-invmgr-oper {

  /*** NAMESPACE / PREFIX DEFINITION ***/

  namespace "http://cisco.com/ns/yang"+
    "/Cisco-IOS-XR-plat-chas-invmgr-oper";


  prefix "plat-chas-invmgr-oper";

  /*** LINKAGE (IMPORTS / INCLUDES) ***/

  import Cisco-IOS-XR-types { prefix "xr"; }

  include Cisco-IOS-XR-plat-chas-invmgr-oper-sub2 {
    revision-date 2015-01-07;
  }

  include Cisco-IOS-XR-plat-chas-invmgr-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR plat-chas-invmgr package operational data.

     This module contains definitions
     for the following management objects:
       platform: Platform information
       platform-inventory: platform inventory

     Copyright (c) 2013-2016 by Cisco Systems, Inc.
     All rights reserved.";

  revision "2015-01-07" {
    description
      "IOS XR 5.3.1 revision.";
  }


  grouping STATE {
    description "Common node of instance, slot";

    container state {
      description "State information";
      uses PLATFORM-INFO;
    }
  }

  grouping PORT-SLOT-TABLE {
    description "Common node of card, module";

    container port-slots {
      description "Table of port slots";

      list port-slot {
        key "name";
        description "Port slot number";

        container port {
          description "Port";
          uses ATTRIBUTES;
        }
        leaf name {
          type xr:Cisco-ios-xr-string;
          description "Port slot name";
        }
        uses SENSOR-TABLE;
        uses ATTRIBUTES;
      }
    }
  }

  grouping SLOT-TABLE {
    description "Common node of rack, rack";

    container slots {
      description "Table of slots";

      list slot {
        key "name";
        description "Slot name";

        container cards {
          description "Table of cards";

          list card {
            key "name";
            description "Card number";

            container hardware-information {
              description "HardwareInformationDir";

              container processor-information {
                description "ProcesorInformation";
                uses INV-PROCESSOR;
              }

              container motherboard-information {
                description "MotherboardInformation";
                uses INV-XML-MOTHERBOARD-INFO;
              }

              container bootflash-information {
                description "BootflashInformation";
                uses INV-BOOTFLASH;
              }

              container disk-information {
                description "DiskInformation";
                uses INV-XML-DISK-INFO;
              }
            }

            container sub-slots {
              description "Table of subslots";

              list sub-slot {
                key "name";
                description "Subslot number";

                container module {
                  description "Module of a subslot";
                  uses PORT-SLOT-TABLE;
                  uses SENSOR-TABLE;
                  uses ATTRIBUTES;
                }
                leaf name {
                  type xr:Cisco-ios-xr-string;
                  description "Subslot name";
                }
                uses ATTRIBUTES;
              }
            }

            container hw-components {
              description "Table of  HW components ";

              list hw-component {
                key "name";
                description "HW component number";
                leaf name {
                  type xr:Cisco-ios-xr-string;
                  description "HW component name";
                }
                uses SENSOR-TABLE;
                uses ATTRIBUTES;
              }
            }
            leaf name {
              type xr:Cisco-ios-xr-string;
              description "Card name";
            }
            uses PORT-SLOT-TABLE;
            uses SENSOR-TABLE;
            uses ATTRIBUTES;
          }
        }
        leaf name {
          type xr:Cisco-ios-xr-string;
          description "Slot name";
        }
        uses ATTRIBUTES;
      }
    }
  }

  grouping PLATFORM-COMMON-SLOT-TABLE {
    description
      "Common node of rack, rackCommon node of rack,
      rack";

    container slots {
      description "Table of slots";

      list slot {
        key "slot-name";
        description "Slot name";

        container instances {
          description "Table of Instances";

          list instance {
            key "instance-name";
            description "Instance name";
            leaf instance-name {
              type string;
              description "Instance name";
            }
            uses STATE;
          }
        }

        container vm {
          description "VM information";
          uses VM-INFO;
        }
        leaf slot-name {
          type xr:Cisco-ios-xr-string;
          description "Slot name";
        }
        uses STATE;
      }
    }
  }

  grouping SENSOR-TABLE {
    description
      "Common node of card, module, hw-component,
      port-slot";

    container sensors {
      description "Table of sensors";

      list sensor {
        key "name";
        description "Sensor number";
        leaf name {
          type xr:Cisco-ios-xr-string;
          description "Sensor name";
        }
        uses ATTRIBUTES;
      }
    }
  }

  grouping ATTRIBUTES {
    description
      "Common node of rack, rack, slot, card, sub-slot,
      module, port-slot, hw-component, sensor, port";

    container attributes {
      description "Attributes";

      container basic-info {
        description "Entity attributes";
        uses INV-XML-ENTITY-BASIC-INFO;
      }

      container fru-info {
        description "Field Replaceable Unit (FRU) attributes";
        uses INV-XML-FRU-INFO;
      }
    }
  }

  container platform {
    config false;
    description "Platform information";

    container racks {
      description "Table of racks";

      list rack {
        key "rack-name";
        description "Rack name";
        leaf rack-name {
          type xr:Cisco-ios-xr-string;
          description "Rack name";
        }
        uses PLATFORM-COMMON-SLOT-TABLE;
      }
    }
  }

  container platform-inventory {
    config false;
    description "platform inventory";

    container racks {
      description "Table of racks";

      list rack {
        key "name";
        description "Rack name";
        leaf name {
          type xr:Cisco-ios-xr-string;
          description "Rack name";
        }
        uses SLOT-TABLE;
        uses ATTRIBUTES;
      }
    }
  }
}
