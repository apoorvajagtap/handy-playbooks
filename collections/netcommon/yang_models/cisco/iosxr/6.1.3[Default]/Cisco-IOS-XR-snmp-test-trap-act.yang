module Cisco-IOS-XR-snmp-test-trap-act {

    namespace "http://cisco.com/ns/yang/Cisco-IOS-XR-snmp-test-trap-act";
    
    prefix "snmp-test-trap-act";
    
    import ietf-inet-types { prefix "inet"; }
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2016 by Cisco Systems, Inc.
     All rights reserved.";
    
    revision "2016-10-25" {
        description
            "IOS XR 6.2.1 revision.";
    }

    rpc snmp-cold-start {
        description "Generate SNMPv2-MIB::coldStart";
    }

    rpc snmp-warm-start {
        description "Generate SNMPv2-MIB::warmStart";
    }
    
    /* description "interface trap commands */
    rpc interface-link-up {
        description "Generate IF-MIB::linkUp";
        input {
            leaf ifindex {
                description
                "interface index for which to generate LinkUp trap";
                type uint32 {
                    range 1..2147483647;
                }
            }
        }
    }

    rpc interface-link-down {
        description "Generate IF-MIB::linkDown";
        input {
            leaf ifindex {
                description
                "interface index for which to generate LinkDown trap";
                type uint32 {
                    range 1..2147483647;
                }
            }
        }
    }

    rpc sonet-section-status {
        description
        "Generate CISCO-SONET-MIB::ciscoSonetSectionStatusChange";
        input {
            leaf ifindex {
                description
                "interface index for which to generate " +
                "ciscoSonetSectionStatusChange trap";
                type uint32 {
                    range 1..2147483647;
                }
            }
        }
    }

    rpc sonet-line-status {
        description
        "Generate CISCO-SONET-MIB::ciscoSonetLineStatusChange";
        input {
            leaf ifindex {
                description
                "interface index for which to generate " +
                "ciscoSonetLineStatusChange trap";
                type uint32 {
                    range 1..2147483647;
                }
            }
        }
    }

    rpc sonet-path-status {
        description
        "Generate CISCO-SONET-MIB::ciscoSonetPathStatusChange";
        input {
            leaf ifindex {
                description "interface index for which to generate " +
                "ciscoSonetPathStatusChange trap";
                type uint32 {
                    range 1..2147483647;
                }
            }
        }
    }

    rpc infra-syslog-message-generated {
        description
            "Generate CISCO-SYSLOG-MIB::clogMessageGenerated";
    }

    rpc infra-flash-device-inserted {
        description 
            "Generate CISCO-FLASH-MIB::ciscoFlashDeviceInsertedNotif";
    }

    rpc infra-flash-device-removed {
        description
            "Generate CISCO-FLASH-MIB::ciscoFlashDeviceRemovedNotif";
    }

    rpc infra-redundancy-progression {
        description
            "Generate CISCO-RF-MIB::ciscoRFProgressionNotif";
    }

    rpc infra-redundancy-switch {
        description
            "Generate CISCO-RF-MIB::ciscoRFSwactNotif";
    }

    rpc infra-bridge-new-root {
        description "Generate BRIDGE-MIB::newRoot";
    }

    rpc infra-bridge-topology-change {
        description "Generate BRIDGE-MIB::topologyChange";
    }

    rpc infra-config-event {
        description "Generate CISCO-CONFIG-MAN-MIB::ciscoConfigManEvent";
    }
    
    rpc entity-sensor-threshold-notification {
        description
            "Generate CISCO-ENTITY-SENSOR-MIB::entSensorThresholdNotification";
        input {
            leaf entindex {
                description
                "entity Physical Index for which to generate trap";
                type uint32 {
                    range 1..2147483647;
                }
            }
        }
    }

    rpc entity-fru-power-status-change-failed {
        description "oper status changed to failed";
        input {
            leaf entindex {
                description
                "entity Physical Index for which to generate trap";
                type uint32 {
                    range 1..2147483647;
                }
            }
        }
    }

    rpc entity-fru-module-status-change-up {
        description "fu trap module status changed as ok";
        input {
            leaf entindex {
                description
                "entity Physical Index for which to generate trap";
                type uint32 {
                    range 1..2147483647;
                }
            }
        }
    }

    rpc entity-fru-module-status-change-down {
        description "fu trap module status changed as failed";
        input {
            leaf entindex {
                description
                "entity Physical Index for which to generate trap";
                type uint32 {
                    range 1..2147483647;
                }
            }
        }
    }

    rpc entity-fru-fan-tray-oper-status-up {
        description "Generate CISCO-ENTITY-FRU-CONTROL-MIB::cefcFanTrayStatusChange";
        input {
            leaf entindex {
                description
                "entity Physical Index for which to generate trap";
                type uint32 {
                    range 1..2147483647;
                }
            }
        }
    }

    rpc entity-fru-fan-tray-inserted {
        description "Generate CISCO-ENTITY-FRU-CONTROL-MIB::cefcFRUInserted";
        input {
            leaf entindex {
                description
                "entity Physical Index for which to generate trap";
                type uint32 {
                    range 1..2147483647;
                }
            }
        }
    }

    rpc entity-fru-fan-tray-removed {
        description "Generate CISCO-ENTITY-FRU-CONTROL-MIB::cefcFRURemoved";
        input {
            leaf entindex {
                description "entity Physical Index for which to generate trap";
                type uint32 {
                    range 1..2147483647;
                }
            }
        }
    }

    rpc platform-hfr-bundle-downed-link {
        description
            "Generate CISCO-FABRIC-HFR-MIB::cfhBundleDownedLinkNotification";
        input {
            leaf bundle-name {
                description
                    "bundle name for which to generate the trap";
                type string;
            }
        }
    }

    rpc platform-hfr-bundle-state {
        description
            "Generate CISCO-FABRIC-HFR-MIB::cfhBundleStateNotification";
        input {
            leaf bundle-name {
                description
                    "bundle name for which to generate the trap";
                type string;
            }
        }
    }

    rpc platform-hfr-plane-state {
        description "Generate CISCO-FABRIC-HFR-MIB::cfhPlaneStateNotification";
        input {
            leaf plane-id {
                description
                    "plane identifier for which to generate the trap";
                type uint32;
            }
        }
    }
    
    rpc routing-bgp-established {
        description
            "Generate BGP4-MIB::bglEstablishedNotification";
    }

    rpc routing-bgp-established-remote-peer {
        description
            "Generate BGP4-MIB::bglEstablishedNotification remote peer";
        input {
            leaf address {
                description
                "BGP remote peer IP address for which to " +
                "generate the trap";
                mandatory true;
                type inet:ipv4-address-no-zone;
            }
        }
    }

    rpc routing-bgp-state-change {
        description
            "Generate CISCO-BGP-MIB::cbgpBackwardTransition";
    }

    rpc routing-bgp-state-change-remote-peer {
        description
            "Generate CISCO-BGP-MIB::cbgpBackwardTransition remote peer";
        input {
            leaf address {
                description
                "BGP remote peer IP address for which to " +
                "generate the trap";
                mandatory true;
                type inet:ipv4-address-no-zone;
            }
        }
    }

    rpc routing-ospf-neighbor-state-change {
        description "Generate OSPF-TRAP-MIB::ospfNbrStateChange";
    }

    rpc routing-ospf-neighbor-state-change-address {
        description "Generate OSPF-TRAP-MIB::ospfNbrStateChange address";
        input {
            leaf address {
                description
                "neighbor's IP source address for which to generate the trap";
                mandatory true;
                type inet:ipv4-address-no-zone;
            }
            leaf ifindex {
                description
                "0 for interfaces having IP addresses or IF-MIB " +
                "ifindex of addressless interface";
                mandatory true;
                type uint32 {
                    range 0..2147483647;
                }
            }
        }
    }
     
    rpc routing-mpls-ldp-session-down {
        description
            "Generate MPLS-LDP-STD-MIB::mplsLdpSessionDown";
    }

    rpc routing-mpls-ldp-session-down-entity-id {
        description
            "Generate MPLS-LDP-STD-MIB::mplsLdpSessionDown entity-id";
        input {
            leaf entity-id {
                description
                    "entity ldp-id in x.x.x.x.y.y format where x.x.x.x " +
                    "is the entity IP address and y.y is the label space";
                mandatory true;
                type string {
                    length 23;
                }
            }
            leaf entity-index {
                description
                    "entity index for which to generate the trap";
                mandatory true;
                type uint32 {
                    range 1..4294967295;
                }
            }
            leaf peer-id {
                description
                    "peer ldp-id in x.x.x.x.y.y format where x.x.x.x is " +
                    "the entity IP address and y.y is the label space";
                mandatory true;
                type string {
                    length 23;
                }
            }
        }
    }

    rpc routing-mpls-tunnel-re-routed {
        description
            "Generate MPLS-TE-STD-MIB::mplsTunnelRerouted";
    }

    rpc routing-mpls-tunnel-re-routed-index {
        description
            "Generate MPLS-TE-STD-MIB::mplsTunnelRerouted index";
        input {
            leaf index {
                description
                "tunnel index for which to generate the trap";
                mandatory true;
                type uint32 {
                    range 0..65535;
                }
            }
            leaf instance {
                description
                "tunnel instance for which to generate the trap";
                mandatory true;
                type uint32 {
                    range 0..65535;
                }
            }
            leaf source {
                description
                "source address for which to generate the trap";
                mandatory true;
                type inet:ipv4-address-no-zone;
            }
            leaf destination {
                description "destination address for which to generate the trap";
                mandatory true;
                type inet:ipv4-address-no-zone;
            }
        }
    }

    rpc routing-mpls-tunnel-re-optimized {
        description
            "Generate MPLS-TE-STD-MIB::mplsTunnelReoptimized";
    }

    rpc routing-mpls-tunnel-re-optimized-index {
        description
            "Generate MPLS-TE-STD-MIB::mplsTunnelReoptimized index";
        input {
            leaf index {
                description
                "tunnel index for which to generate the trap";
                mandatory true;
                type uint32 {
                    range 0..65535;
                }
            }
            leaf instance {
                description
                "tunnel instance for which to generate the trap";
                mandatory true;
                type uint32 {
                    range 0..65535;
                }
            }
            leaf source {
                description
                "source address for which to generate the trap";
                mandatory true;
                type inet:ipv4-address-no-zone;
            }
            leaf destination {
                description
                "destination address for which to generate the trap";
                mandatory true;
                type inet:ipv4-address-no-zone;
            }
        }
    }

    rpc routing-mpls-tunnel-down {
        description
            "Generate MPLS-TE-STD-MIB::mplsTunnelDown";
    }

    rpc routing-mpls-tunnel-down-index {
        description
            "Generate MPLS-TE-STD-MIB::mplsTunnelDown index";
        input {
            leaf index {
                description
                "tunnel index for which to generate the trap";
                mandatory true;
                type uint32 {
                    range 0..65535;
                }
            }
            leaf instance {
                description
                "tunnel instance for which to generate the trap";
                mandatory true;
                type uint32 {
                    range 0..65535;
                }
            }
            leaf source {
                description "src address";
                mandatory true;
                type inet:ipv4-address-no-zone;
            }
            leaf destination {
                description
                "destination address for which to generate the trap";
                mandatory true;
                type inet:ipv4-address-no-zone;
            }
        }
    }

    rpc all {
        description "generate all the supported traps";
    }
}
