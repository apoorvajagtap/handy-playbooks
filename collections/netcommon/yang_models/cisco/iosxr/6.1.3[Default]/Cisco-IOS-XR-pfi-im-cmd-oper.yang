module Cisco-IOS-XR-pfi-im-cmd-oper {

  /*** NAMESPACE / PREFIX DEFINITION ***/

  namespace "http://cisco.com/ns/yang/Cisco-IOS-XR-pfi-im-cmd-oper";


  prefix "pfi-im-cmd-oper";

  /*** LINKAGE (IMPORTS / INCLUDES) ***/

  import Cisco-IOS-XR-types { prefix "xr"; }

  include Cisco-IOS-XR-pfi-im-cmd-oper-sub2 {
    revision-date 2016-12-18;
  }

  include Cisco-IOS-XR-pfi-im-cmd-oper-sub1 {
    revision-date 2016-12-18;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pfi-im-cmd package operational data.

     This module contains definitions
     for the following management objects:
       interfaces: Interface operational data

     Copyright (c) 2013-2016 by Cisco Systems, Inc.
     All rights reserved.";

  revision "2016-12-18" {
    description
      "Description updated.";
  }

  revision "2015-11-09" {
    description
      "IOS XR 6.0 revision.";
  }

  typedef Interface-type-set {
    type enumeration {
      enum hardware-interfaces {
        value 0;
        description
          "Restrict the output to hardware interfaces only";
      }
    }
    description "Interface type set";
  }

  grouping INTERFACE-SUMMARY {
    description "Common node of node-type-set, interfaces";

    container interface-summary {
      description "Interface summary information";
      uses IM-IF-SUMMARY-INFO;
    }
  }

  container interfaces {
    config false;
    description "Interface operational data";

    container interface-xr {
      description
        "Detailed operational data for interfaces and
        configured features";

      list interface {
        key "interface-name";
        description
          "Detailed operational data for a particular
          interface";
        leaf interface-name {
          type xr:Interface-name;
          description "The name of the interface";
        }
        uses IM-CMD-INFO;
      }
    }

    container node-type-sets {
      description
        "Node and/or interface type specific view of
        interface summary data";

      list node-type-set {
        description
          "Summary data for all interfaces on a particular
          node";
        leaf node-name {
          type xr:Node-id;
          description "The location to filter on";
        }
        leaf type-set-name {
          type Interface-type-set;
          description "The interface type to filter on";
        }
        uses INTERFACE-SUMMARY;
      }
    }

    container interface-briefs {
      description "Brief operational data for interfaces";

      list interface-brief {
        key "interface-name";
        description
          "Brief operational attributes for a particular
          interface";
        leaf interface-name {
          type xr:Interface-name;
          description "The name of the interface";
        }
        uses IMDS-IFATTR-BASE-INFO;
      }
    }

    container inventory-summary {
      description "Inventory summary information";
      uses IM-IF-SUMMARY-INFO;
    }

    container interfaces {
      description "Descriptions for interfaces";

      list interface {
        key "interface-name";
        description "Description for a particular interface";
        leaf interface-name {
          type xr:Interface-name;
          description "The name of the interface";
        }
        uses IM-DESC-INFO;
      }
    }
    uses INTERFACE-SUMMARY;
  }
}
